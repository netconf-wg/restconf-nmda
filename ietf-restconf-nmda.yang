module ietf-restconf-nmda {
  yang-version 1.1;
  namespace "urn:ietf:params:xml:ns:yang:ietf-restconf-nmda";
  prefix "rn";

  import ietf-restconf {
    prefix rc;
    reference "RFC 8040: RESTCONF Protocol";
  }

  import ietf-datastores {
    prefix ds;
    reference "I-D.netmod-revised-datastores";
  }

  organization
    "IETF NETCONF (Network Configuration) Working Group";

  contact
    "WG Web:   <http://tools.ietf.org/wg/netconf/>
     WG List:  <mailto:netconf@ietf.org>

     Author:   Martin Bjorklund
               <mailto:mbj@tail-f.com>

     Author:   Juergen Schoenwaelder
               <mailto:j.schoenwaelder@jacobs-university.de>

     Author:   Phil Shafer
               <mailto:phil@juniper.net>

     Author:   Kent Watsen
               <mailto:kwatsen@juniper.net>

     Author:   Rob Wilton
               <rwilton@cisco.com>";

  description
    "This module augments ietf-restconf to define a new top-level
     resource called 'datastores', which can both return a list
     of datastores supported by the server, as well as act as a
     mount-point for those datastores.  

     Copyright (c) 2016 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: replace XXXX with actual RFC number and remove this
  // note.

  // RFC Ed.: update the date below with the date of RFC publication
  // and remove this note.
  revision 2017-06-02 {
    description
      "Initial revision.";
    reference
      "RFC XXXX: RESTCONF Protocol.";
  }

  augment "/rc:yang-api/restconf/" {
    container datastores {
      config false;
      description
        "This resource serves two purposes.  The first is as this
         YANG model shows, a flat list of datastores supported by the
         server.  The second purpose is to act as a mount-point for the
         listed datastores e.g., {+restconf}/datastores/<datastore>/.
         Please see RFC XXXX for details.";
      leaf-list datastore {
        type identityref {
          base ds:datastore;
        }
        description
          "A datastore supported by this server.";
      }
    }
  }

}
